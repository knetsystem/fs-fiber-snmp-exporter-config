-- *****************************************************************
-- FS-FIBER-MIB.mib:  FS FIBER MIB file
--
-- January 2012, wangyouliang
--
-- Copyright © 2009-2020 FS.COM Inc.
-- All rights reserved.
-- 
-- *****************************************************************
--

FS-FIBER-MIB DEFINITIONS ::= BEGIN

IMPORTS
        MODULE-IDENTITY,
        OBJECT-TYPE
                FROM SNMPv2-SMI
        TruthValue,
        DisplayString
                FROM SNMPv2-TC
        MODULE-COMPLIANCE,
        OBJECT-GROUP
                FROM SNMPv2-CONF
        IfIndex
                FROM FS-TC
        fsMgmt
                FROM FS-SMI;

fsFiberMIB MODULE-IDENTITY
        LAST-UPDATED "201111280000Z"
        ORGANIZATION "FS.COM Inc."
        CONTACT-INFO
                " 
                Tel: 400-865-2852 

                E-mail: https://www.fs.com/live_chat_service_mail.html"
        DESCRIPTION
                "This module defines fs fiber module information mibs."
        REVISION      "201111280000Z"
        DESCRIPTION
                "Initial version of this MIB module."
        ::= { fsMgmt 105}

fsFiberMIBObjects OBJECT IDENTIFIER ::= { fsFiberMIB 1 }


-- ---------------------------------------------------------- --
-- A table for getting Fiber port information.
-- ---------------------------------------------------------- -- 
fsFiberTable OBJECT-TYPE
        SYNTAX SEQUENCE OF FSFiberEntry
        MAX-ACCESS not-accessible
        STATUS current
        DESCRIPTION
            "A table for getting Fiber Module information"
        ::= { fsFiberMIBObjects 1 }
    
fsFiberEntry OBJECT-TYPE
        SYNTAX FSFiberEntry
        MAX-ACCESS not-accessible
        STATUS current
        DESCRIPTION
            "Entry of a Fiber Module information."
        INDEX { fsFiberPortIndex }
        ::= { fsFiberTable 1 }
    
FSFiberEntry ::=
        SEQUENCE {
                fsFiberPortIndex IfIndex,
                fsFiberPortDescr DisplayString,
                fsFiberTransceiverType INTEGER,
                fsFiberConnectorType INTEGER,
                fsFiberWavelength INTEGER,
                fsFiberTransferDistanceSMF INTEGER,
                fsFiberTransferDistance62point5umOM1 INTEGER,
                fsFiberTransferDistance62point5um INTEGER,
                fsFiberTransferDistance50umOM2 INTEGER,
                fsFiberTransferDistance50um INTEGER,
                fsFiberTransferDistance50umOM3 INTEGER,
                fsFiberTransferDistanceEBW50um INTEGER,
                fsFiberTransferDistanceCopper INTEGER,
                fsFiberTransferDistanceCableAssembly INTEGER,
                fsFiberDDMSupportStatus TruthValue,
                fsFiberSerialNumber DisplayString,
                fsFiberTemp INTEGER,
                fsFiberTempStatus INTEGER,
                fsFiberVoltage INTEGER,
                fsFiberVoltageStatus INTEGER,
                fsFiberBias INTEGER,
                fsFiberBiasStatus INTEGER,
                fsFiberChannel1Bias INTEGER,
                fsFiberChannel1BiasStatus INTEGER,
                fsFiberChannel2Bias INTEGER,
                fsFiberChannel2BiasStatus INTEGER,
                fsFiberChannel3Bias INTEGER,
                fsFiberChannel3BiasStatus INTEGER,
                fsFiberChannel4Bias INTEGER,
                fsFiberChannel4BiasStatus INTEGER,
                fsFiberRXpowerIntegerpart INTEGER,
                fsFiberRXpowerDecimalpart INTEGER,
                fsFiberRXpowertype INTEGER,
                fsFiberRXpowerStatus INTEGER,
                fsFiberChannel1RXpowerIntegerpart INTEGER,
                fsFiberChannel1RXpowerDecimalpart INTEGER,
                fsFiberChannel1RXpowertype INTEGER,
                fsFiberChannel1RXpowerStatus INTEGER,
                fsFiberChannel2RXpowerIntegerpart INTEGER,
                fsFiberChannel2RXpowerDecimalpart INTEGER,
                fsFiberChannel2RXpowertype INTEGER,
                fsFiberChannel2RXpowerStatus INTEGER,
                fsFiberChannel3RXpowerIntegerpart INTEGER,
                fsFiberChannel3RXpowerDecimalpart INTEGER,
                fsFiberChannel3RXpowertype INTEGER,
                fsFiberChannel3RXpowerStatus INTEGER,
                fsFiberChannel4RXpowerIntegerpart INTEGER,
                fsFiberChannel4RXpowerDecimalpart INTEGER,
                fsFiberChannel4RXpowertype INTEGER,
                fsFiberChannel4RXpowerStatus INTEGER,
                fsFiberTXpowerIntegerpart INTEGER,
                fsFiberTXpowerDecimalpart INTEGER,
                fsFiberTXpowerStatus INTEGER,
                fsFiberChannel1TXpowerIntegerpart INTEGER,
                fsFiberChannel1TXpowerDecimalpart INTEGER,
                fsFiberChannel1TXpowerStatus INTEGER,
                fsFiberChannel2TXpowerIntegerpart INTEGER,
                fsFiberChannel2TXpowerDecimalpart INTEGER,
                fsFiberChannel2TXpowerStatus INTEGER,
                fsFiberChannel3TXpowerIntegerpart INTEGER,
                fsFiberChannel3TXpowerDecimalpart INTEGER,
                fsFiberChannel3TXpowerStatus INTEGER,
                fsFiberChannel4TXpowerIntegerpart INTEGER,
                fsFiberChannel4TXpowerDecimalpart INTEGER,
                fsFiberChannel4TXpowerStatus INTEGER
        }
        
fsFiberPortIndex OBJECT-TYPE
        SYNTAX IfIndex
        MAX-ACCESS not-accessible
        STATUS current
        DESCRIPTION
            "Port index of the port."
        ::= { fsFiberEntry 1 }

fsFiberPortDescr OBJECT-TYPE
        SYNTAX DisplayString (SIZE(1..32))
        MAX-ACCESS read-only
        STATUS current
        DESCRIPTION
            "Discription of the port."
        ::= { fsFiberEntry 2 }

fsFiberTransceiverType OBJECT-TYPE
        SYNTAX INTEGER {
            unknown(1),
            fiber100BASEGTSFP(2),
            fiber100BASESXSFP(3),
            fiber100BASELXSFP(4),
            fiber100BASELHSFP(5),
	    fiber100BASEZXSFP(6),
            fiber100CopperSFP(7),
            fiber1000BASEGTSFP(8),
            fiber1000BASESXSFP(9),
            fiber1000BASELXSFP(10),
            fiber1000BASELHSFP(11),
	    fiber1000BASEZXSFP(12),
            fiber1000CopperSFP(13),
            fiber10GCopperSFPPlus(14),
            fiber10GBASESRSFPPlus(15),
            fiber10GBASELRSFPPlus(16),
            fiber10GBASEERSFPPlus(17),
            fiber10GBASEZRSFPPlus(18),
            fiber10GCopperXFP(19),
            fiber10GBASESRXFP(20),
            fiber10GBASELRXFP(21),
            fiber10GBASEERXFP(22),
            fiber10GBASEZRXFP(23),
            fiber40GActiveCableQSFPPlus(24),
            fiber40GLR4QSFPPlus(25),
            fiber40GCopperQSFPPlus(26),
            fiber40GSR4QSFPPlus(27),
            fiber2500CopperSFP(28),
            fiberFC16G(29),
            fiberFC8G(30),
            fiberFC4G(31),
            fiberFC2G(32),
            fiber10GActiveCableSFPPlus(33)
        }
        MAX-ACCESS read-only
        STATUS current
        DESCRIPTION
            "Transceiver type of the Fiber module insered into the port."
        ::= { fsFiberEntry 3 }

fsFiberConnectorType OBJECT-TYPE
        SYNTAX INTEGER {
	    meaningless(0),
            unknownorunspecified(1),
            vendorspecific(2),
            sc(3),
            fiberChannelStyle1CopperConnector(4),
            fiberChannelStyle2CopperConnector(5),
            bncortnc(6),
            fiberChannelCoaxialHeaders(7),
            fiberJack(8),
            lc(9),
            mtrj(10),
            mu(11),
            sg(12),
            opticalPigtail(13),
            hssdcII(14),
            copperPigtail(15),
	    mpo(16),
	    rj45(17),
            noSparableConnector(18)
        }
        MAX-ACCESS read-only
        STATUS current
        DESCRIPTION
            "Connector type of the Fiber module insered into the port.
	     If the transceiver type of Fiber module is unknown(1), then this
             object contains a zero value."
        ::= { fsFiberEntry 4 }

fsFiberWavelength OBJECT-TYPE
        SYNTAX INTEGER
        MAX-ACCESS read-only
        STATUS current
        DESCRIPTION
            "The value of wavelength of the Fiber module insered into the port.
	     If the transceiver type of Fiber module is either fiber100CopperSFP(7)  
	     or fiber1000CopperSFP(13) (or fiber10GCopperSFPPlus(14), 
	     or fiber10GCopperXFP(19), or fiber40GCopperQSFPPlus(26), or fiber2500CopperSFP(28), or unknown(1)), then this
             object contains a zero value."
        ::= { fsFiberEntry 5 }

fsFiberTransferDistanceSMF OBJECT-TYPE
        SYNTAX INTEGER
        MAX-ACCESS read-only
        STATUS current
        DESCRIPTION
            "The value of transfer distance of the Fiber module insered into the port.
	     This value specifies the link length that is supported by the 
	     transceiver while operating in compliance with the applicable 
	     standards using single mode fiber for. The value is in units of kilometers.
	     A value of zero means that the transceiver does not support single mode fiber."
        ::= { fsFiberEntry 6 }

fsFiberTransferDistance62point5umOM1 OBJECT-TYPE
        SYNTAX INTEGER
        MAX-ACCESS read-only
        STATUS current
        DESCRIPTION
            "The value of transfer distance of the Fiber module insered into the port.
	     This value specifies the link length that is supported by the 
	     transceiver while operating in compliance with the applicable 
	     standards using 62.5 micron multimode (200 MHz*Km at 850 nm, 500 MHz*Km 
	     at 1310 nm) fiber. The value is in units of meters.
	     A value of zero means that the transceiver does not 
	     support 62.5 micron multimode fiber or the Fiber module type 
	     is neither SFP/SFP+ nor QSFP+."
        ::= { fsFiberEntry 7 }

fsFiberTransferDistance62point5um OBJECT-TYPE
        SYNTAX INTEGER
        MAX-ACCESS read-only
        STATUS current
        DESCRIPTION
            "The value of transfer distance of the Fiber module insered into the port.
	     This value specifies the link length that is supported by the 
	     transceiver while operating in compliance with the applicable 
	     standards using 62.5 micron core multimode (200 MHz*Km at 850 nm, 500 MHz*Km 
	     at 1310 nm) fiber. The value is in units of meters.
	     A value of zero means that the transceiver does not 
	     support 62.5 micron multimode fiber or the Fiber module type is not XFP."
        ::= { fsFiberEntry 8 }

fsFiberTransferDistance50umOM2 OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron multimode (500 MHz*Km at 850 nm for SFP module 
	     or at 850 nm and 1310 nm for QSFP+ module) fiber. The value is in units of meters.
	     A value of zero means that the transceiver does not 
	     support 50 micron multimode fiber or the Fiber module type 
	     is neither SFP/SFP+ nor QSFP+."
        ::= { fsFiberEntry 9 }

fsFiberTransferDistance50um OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron core multimode (500 MHz*Km at 850 nm and 1310 nm) fiber. 
	     The value is in units of meters.
	     A value of zero means that the transceiver does not 
	     support 50 micron core multimode fiber or the Fiber module type 
	     is not XFP."
        ::= { fsFiberEntry 10 }

fsFiberTransferDistance50umOM3 OBJECT-TYPE
        SYNTAX INTEGER
        MAX-ACCESS read-only
        STATUS current
        DESCRIPTION
            "The value of transfer distance of the Fiber module insered into the port.
	     This value specifies the link length that is supported by the 
	     transceiver while operating in compliance with the applicable 
	     standards using 50 micron multimode OM3(2000 MHz*Km) fiber. 
	     The value is in units of meters.
	     A value of zero means that the transceiver does not 
	     support 50 micron multimode fiber or the Fiber module type 
	     is neither SFP/SFP+ nor QSFP+."
        ::= { fsFiberEntry 11 }

fsFiberTransferDistanceEBW50um OBJECT-TYPE
        SYNTAX INTEGER
        MAX-ACCESS read-only
        STATUS current
        DESCRIPTION
            "The value of transfer distance of the Fiber module insered into the port.
	     This value specifies the link length that is supported by the 
	     transceiver while operating in compliance with the applicable 
	     standards using 2000 MHz*Km (850nm) extended bandwidth 50 
	     micron core multimode fiber. The value is in units of meters.  
	     A value of zero means that the transceiver does not support 
	     extended bandwidth 50 micron multimode fiber or the Fiber module type is not XFP."
        ::= { fsFiberEntry 12 }

fsFiberTransferDistanceCopper OBJECT-TYPE
        SYNTAX INTEGER
        MAX-ACCESS read-only
        STATUS current
        DESCRIPTION
            "The value of transfer distance of the Fiber module insered into the port.
	     This value specifies the link length that is supported by the 
	     transceiver while operating in compliance with the applicable 
	     standards using copper cables. The value is in units of meters.
	     A value of zero means that the transceiver does not support copper cables
	     or the Fiber module type is neither SFP/SFP+ nor XFP."
        ::= { fsFiberEntry 13 }

fsFiberTransferDistanceCableAssembly OBJECT-TYPE
        SYNTAX INTEGER
        MAX-ACCESS read-only
        STATUS current
        DESCRIPTION
            "The value of transfer distance of the Fiber module insered into the port.
	     This value specifies the link length of the Cable assembly passive. 
	     The value is in units of meters.
	     A value of zero means that the transceiver is not a cable assemblyor
	     or the Fiber module type is not QSFP+."
        ::= { fsFiberEntry 14 }

fsFiberDDMSupportStatus OBJECT-TYPE
        SYNTAX        TruthValue
        MAX-ACCESS    read-only
        STATUS        current
        DESCRIPTION
        "This object indicates that whether the Digital Diagnostic Monitors is implemeted."
    ::= { fsFiberEntry 15 }

fsFiberSerialNumber OBJECT-TYPE
        SYNTAX DisplayString (SIZE(1..32))
        MAX-ACCESS read-only
        STATUS current
        DESCRIPTION
            "The serial number of the Fiber module insered into the port."
        ::= { fsFiberEntry 16 }

fsFiberTemp OBJECT-TYPE
        SYNTAX INTEGER
        MAX-ACCESS read-only
        STATUS current
        DESCRIPTION
            "The temperature of the Fiber module insered into the port.
	    The value is in units of degrees Celsius.
	    If the fsFiberDDMSupportStatus is false, the temperature value is 0."
        ::= { fsFiberEntry 17 }

fsFiberTempStatus OBJECT-TYPE
        SYNTAX INTEGER {
            unknown(1),
            ok(2),
            warning(3),
            alarm(4)
        }
        MAX-ACCESS read-only
        STATUS current
        DESCRIPTION
            "The status ok(2) indicates that the temperature of the Fiber module is in
	    the normal level. The status warning(3) indicates that the temperature of 
	    the Fiber module exceeds high warning level or is below low warning level. 
            The status alarm(4) indicates that the temperature of 
	    the Fiber module exceeds high alarm level or is below low alarm level. 
	    If the fsFiberDDMSupportStatus is false or the Fiber module type is 
	    neither SFP/SFP+ nor XFP(or not QSFP+), the status is unknown(1)."
        ::= { fsFiberEntry 18 }

fsFiberVoltage OBJECT-TYPE
        SYNTAX INTEGER
        MAX-ACCESS read-only
        STATUS current
        DESCRIPTION
            "The voltage of the Fiber module insered into the port.
	    The value is in units of mVolts.
	    If the fsFiberDDMSupportStatus is false, the voltage value is 0."
        ::= { fsFiberEntry 19 }

fsFiberVoltageStatus OBJECT-TYPE
        SYNTAX INTEGER {
            unknown(1),
            ok(2),
            warning(3),
            alarm(4)
        }
        MAX-ACCESS read-only
        STATUS current
        DESCRIPTION
            "The status ok(2) indicates that the voltage of the Fiber module is in
	    the normal level. The status warning(3) indicates that the voltage of 
	    the Fiber module exceeds high warning level or is below low warning level. 
            The status alarm(4) indicates that the voltage of 
	    the Fiber module exceeds high alarm level or is below low alarm level. 
	    If the fsFiberDDMSupportStatus is false or the Fiber module type is 
	    neither SFP/SFP+ nor XFP(or not QSFP+), the status is unknown(1)."
        ::= { fsFiberEntry 20 }

fsFiberBias OBJECT-TYPE
        SYNTAX INTEGER
        MAX-ACCESS read-only
        STATUS current
        DESCRIPTION
            "The bias of the Fiber module insered into the port.
	    The value is in units of uA.
	    If the fsFiberDDMSupportStatus is false or the Fiber module type is 
	    neither SFP/SFP+ nor XFP, the bias value is 0."
        ::= { fsFiberEntry 21 }

fsFiberBiasStatus OBJECT-TYPE
        SYNTAX INTEGER {
            unknown(1),
            ok(2),
            warning(3),
            alarm(4)
        }
        MAX-ACCESS read-only
        STATUS current
        DESCRIPTION
            "The status ok(2) indicates that the bias of the Fiber module is in
	    the normal level. The status warning(3) indicates that the bias of 
	    the Fiber module exceeds high warning level or is below low warning level. 
            The status alarm(4) indicates that the bias of 
	    the Fiber module exceeds high alarm level or is below low alarm level. 
	    If the fsFiberDDMSupportStatus is false or the Fiber module type is 
	    neither SFP/SFP+ nor XFP, the status is unknown(1)."
        ::= { fsFiberEntry 22 }

fsFiberChannel1Bias OBJECT-TYPE
        SYNTAX INTEGER
        MAX-ACCESS read-only
        STATUS current
        DESCRIPTION
            "The bias in Channel 1 of the QSFP+ Fiber module insered into the port.
	    The value is in units of uA.
	    If the fsFiberDDMSupportStatus is false or the Fiber module type is 
	    not QSFP+, the bias value in Channel 1 is 0."
        ::= { fsFiberEntry 23 }

fsFiberChannel1BiasStatus OBJECT-TYPE
        SYNTAX INTEGER {
            unknown(1),
            ok(2),
            warning(3),
            alarm(4)
        }
        MAX-ACCESS read-only
        STATUS current
        DESCRIPTION
            "The status ok(2) indicates that the bias in the Channel 1 of QSFP+ is in
	    the normal level. The status warning(3) indicates 
	    that the bias in the Channel 1 exceeds high warning level or is 
	    below low warning level. The status alarm(4) indicates that the bias in 
	    the Channel 1 exceeds high alarm level or is below low alarm level. 
	    If the fsFiberDDMSupportStatus is false or the Fiber module type is 
	    not QSFP+, the status is unknown(1)."
        ::= { fsFiberEntry 24 }

fsFiberChannel2Bias OBJECT-TYPE
        SYNTAX INTEGER
        MAX-ACCESS read-only
        STATUS current
        DESCRIPTION
            "The bias in Channel 2 of the QSFP+ Fiber module insered into the port.
	    The value is in units of uA.
	    If the fsFiberDDMSupportStatus is false or the Fiber module type is 
	    not QSFP+, the bias value in Channel 2 is 0."
        ::= { fsFiberEntry 25 }

fsFiberChannel2BiasStatus OBJECT-TYPE
        SYNTAX INTEGER {
            unknown(1),
            ok(2),
            warning(3),
            alarm(4)
        }
        MAX-ACCESS read-only
        STATUS current
        DESCRIPTION
            "The status ok(2) indicates that the bias in the Channel 2 of QSFP+ is in
	    the normal level. The status warning(3) indicates 
	    that the bias in the Channel 2 exceeds high warning level or is 
	    below low warning level. The status alarm(4) indicates that the bias in 
	    the Channel 2 exceeds high alarm level or is below low alarm level. 
	    If the fsFiberDDMSupportStatus is false or the Fiber module type is 
	    not QSFP+, the status is unknown(1)."
        ::= { fsFiberEntry 26 }

fsFiberChannel3Bias OBJECT-TYPE
        SYNTAX INTEGER
        MAX-ACCESS read-only
        STATUS current
        DESCRIPTION
            "The bias in Channel 3 of the QSFP+ Fiber module insered into the port.
	    The value is in units of uA.
	    If the fsFiberDDMSupportStatus is false or the Fiber module type is 
	    not QSFP+, the bias value in Channel 3 is 0."
        ::= { fsFiberEntry 27 }

fsFiberChannel3BiasStatus OBJECT-TYPE
        SYNTAX INTEGER {
            unknown(1),
            ok(2),
            warning(3),
            alarm(4)
        }
        MAX-ACCESS read-only
        STATUS current
        DESCRIPTION
            "The status ok(2) indicates that the bias in the Channel 3 of QSFP+ is in
	    the normal level. The status warning(3) indicates 
	    that the bias in the Channel 3 exceeds high warning level or is 
	    below low warning level. The status alarm(4) indicates that the bias in 
	    the Channel 3 exceeds high alarm level or is below low alarm level. 
	    If the fsFiberDDMSupportStatus is false or the Fiber module type is 
	    not QSFP+, the status is unknown(1)."
        ::= { fsFiberEntry 28 }

fsFiberChannel4Bias OBJECT-TYPE
        SYNTAX INTEGER
        MAX-ACCESS read-only
        STATUS current
        DESCRIPTION
            "The bias in Channel 4 of the QSFP+ Fiber module insered into the port.
	    The value is in units of uA.
	    If the fsFiberDDMSupportStatus is false or the Fiber module type is 
	    not QSFP+, the bias value in Channel 4 is 0."
        ::= { fsFiberEntry 29 }

fsFiberChannel4BiasStatus OBJECT-TYPE
        SYNTAX INTEGER {
            unknown(1),
            ok(2),
            warning(3),
            alarm(4)
        }
        MAX-ACCESS read-only
        STATUS current
        DESCRIPTION
            "The status ok(2) indicates that the bias in the Channel 4 of QSFP+ is in
	    the normal level. The status warning(3) indicates 
	    that the bias in the Channel 4 exceeds high warning level or is 
	    below low warning level. The status alarm(4) indicates that the bias in 
	    the Channel 4 exceeds high alarm level or is below low alarm level. 
	    If the fsFiberDDMSupportStatus is false or the Fiber module type is 
	    not QSFP+, the status is unknown(1)."
        ::= { fsFiberEntry 30 }

fsFiberRXpowerIntegerpart OBJECT-TYPE
        SYNTAX INTEGER
        MAX-ACCESS read-only
        STATUS current
        DESCRIPTION
            "The integer part of Rx power of the Fiber module insered into the port.
	    The value is in units of dbm.
	    If the fsFiberDDMSupportStatus is false or the Fiber module type is 
	    neither SFP/SFP+ nor XFP, the integer part of Rx power value 
	    is -100(means that the value is invalid)."
        ::= { fsFiberEntry 31 }

fsFiberRXpowerDecimalpart OBJECT-TYPE
        SYNTAX INTEGER
        MAX-ACCESS read-only
        STATUS current
        DESCRIPTION
            "The decimal part of Rx power of the Fiber module insered into the port.
	    The value is in units of dbm.
	    If the fsFiberDDMSupportStatus is false or the Fiber module type is 
	    neither SFP/SFP+ nor XFP, the decimal part of Rx power value 
	    is -100(means that the value is invalid)."
        ::= { fsFiberEntry 32 }

fsFiberRXpowertype OBJECT-TYPE
        SYNTAX INTEGER {
            unknown(1),
            average(2),
            oma(3)
        }
        MAX-ACCESS read-only
        STATUS current
        DESCRIPTION
            "The value indicates whether the received power measurement 
	     represents average input optical power(2) or oma(3). 
	     If the fsFiberDDMSupportStatus is false or the Fiber module type is 
	     neither SFP/SFP+ nor XFP (or not QSFP+), the value is unknown(1)."
        ::= { fsFiberEntry 33 }

fsFiberRXpowerStatus OBJECT-TYPE
        SYNTAX INTEGER {
            unknown(1),
            ok(2),
            warning(3),
            alarm(4)
        }
        MAX-ACCESS read-only
        STATUS current
        DESCRIPTION
            "The status ok(2) indicates that the Rx power of the Fiber module is in
	    the normal level. The status warning(3) indicates that the Rx power of 
	    the Fiber module exceeds high warning level or is below low warning level. 
            The status alarm(4) indicates that the Rx power of 
	    the Fiber module exceeds high alarm level or is below low alarm level. 
	    If the fsFiberDDMSupportStatus is false or the Fiber module type is 
	    neither SFP/SFP+ nor XFP, the status is unknown(1)."
        ::= { fsFiberEntry 34 }

fsFiberChannel1RXpowerIntegerpart OBJECT-TYPE
        SYNTAX INTEGER
        MAX-ACCESS read-only
        STATUS current
        DESCRIPTION
            "The integer part of Rx power in Channel 1 of the QSFP+ 
	    Fiber module insered into the port. The value is in units of dbm.
	    If the fsFiberDDMSupportStatus is false or the Fiber module type is 
	    not QSFP+, the integer part of Rx power value in Channel 1 
	    is -100(means the value is invalid)."
        ::= { fsFiberEntry 35 }

fsFiberChannel1RXpowerDecimalpart OBJECT-TYPE
        SYNTAX INTEGER
        MAX-ACCESS read-only
        STATUS current
        DESCRIPTION
            "The decimal part of Rx power in Channel 1 of the QSFP+ 
	    Fiber module insered into the port. The value is in units of dbm.
	    If the fsFiberDDMSupportStatus is false or the Fiber module type is 
	    not QSFP+, the decimal part of Rx power value in Channel 1 
	    is -100(means the value is invalid)."
        ::= { fsFiberEntry 36 }

fsFiberChannel1RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 1 of QSFP+. 
	     If the fsFiberDDMSupportStatus is false or the Fiber module type is 
	     not QSFP+, the value is unknown(1)."
        ::= { fsFiberEntry 37 }

fsFiberChannel1RXpowerStatus OBJECT-TYPE
        SYNTAX INTEGER {
            unknown(1),
            ok(2),
            warning(3),
            alarm(4)
        }
        MAX-ACCESS read-only
        STATUS current
        DESCRIPTION
            "The status ok(2) indicates that the Rx power in the Channel 1 of QSFP+ is in
	    the normal level. The status warning(3) indicates that 
	    the Rx power in the Channel 1 exceeds high warning level or is below 
	    low warning level. The status alarm(4) indicates that the Rx power in the
	    Channel 1 exceeds high alarm level or is below low alarm level. 
	    If the fsFiberDDMSupportStatus is false or the Fiber module type is 
	    not QSFP+, the status is unknown(1)."
        ::= { fsFiberEntry 38 }

fsFiberChannel2RXpowerIntegerpart OBJECT-TYPE
        SYNTAX INTEGER
        MAX-ACCESS read-only
        STATUS current
        DESCRIPTION
            "The integer part of Rx power in Channel 1 of the QSFP+ 
	    Fiber module insered into the port. The value is in units of dbm.
	    If the fsFiberDDMSupportStatus is false or the Fiber module type is 
	    not QSFP+, the integer part of Rx power value in Channel 1 
	    is -100(means the value is invalid)."
        ::= { fsFiberEntry 39 }

fsFiberChannel2RXpowerDecimalpart OBJECT-TYPE
        SYNTAX INTEGER
        MAX-ACCESS read-only
        STATUS current
        DESCRIPTION
            "The decimal part of Rx power in Channel 1 of the QSFP+ 
	    Fiber module insered into the port. The value is in units of dbm.
	    If the fsFiberDDMSupportStatus is false or the Fiber module type is 
	    not QSFP+, the decimal part of Rx power value in Channel 2 
	    is -100(means the value is invalid)."
        ::= { fsFiberEntry 40 }

fsFiberChannel2RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 2 of QSFP+. 
	     If the fsFiberDDMSupportStatus is false or the Fiber module type is 
	     not QSFP+, the value is unknown(1)."
        ::= { fsFiberEntry 41 }

fsFiberChannel2RXpowerStatus OBJECT-TYPE
        SYNTAX INTEGER {
            unknown(1),
            ok(2),
            warning(3),
            alarm(4)
        }
        MAX-ACCESS read-only
        STATUS current
        DESCRIPTION
            "The status ok(2) indicates that the Rx power in the Channel 2 of QSFP+ is in
	    the normal level. The status warning(3) indicates that 
	    the Rx power in the Channel 2 exceeds high warning level or is below 
	    low warning level. The status alarm(4) indicates that the Rx power in the
	    Channel 2 exceeds high alarm level or is below low alarm level. 
	    If the fsFiberDDMSupportStatus is false or the Fiber module type is 
	    not QSFP+, the status is unknown(1)."
        ::= { fsFiberEntry 42 }

fsFiberChannel3RXpowerIntegerpart OBJECT-TYPE
        SYNTAX INTEGER
        MAX-ACCESS read-only
        STATUS current
        DESCRIPTION
            "The integer part of Rx power in Channel 3 of the QSFP+ 
	    Fiber module insered into the port. The value is in units of dbm.
	    If the fsFiberDDMSupportStatus is false or the Fiber module type is 
	    not QSFP+, the integer part of Rx power value in Channel 3 
	    is -100(means the value is invalid)."
        ::= { fsFiberEntry 43 }

fsFiberChannel3RXpowerDecimalpart OBJECT-TYPE
        SYNTAX INTEGER
        MAX-ACCESS read-only
        STATUS current
        DESCRIPTION
            "The decimal part of Rx power in Channel 3 of the QSFP+ 
	    Fiber module insered into the port. The value is in units of dbm.
	    If the fsFiberDDMSupportStatus is false or the Fiber module type is 
	    not QSFP+, the decimal part of Rx power value in Channel 3 
	    is -100(means the value is invalid)."
        ::= { fsFiberEntry 44 }

fsFiberChannel3RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 3 of QSFP+. 
	     If the fsFiberDDMSupportStatus is false or the Fiber module type is 
	     not QSFP+, the value is unknown(1)."
        ::= { fsFiberEntry 45 }

fsFiberChannel3RXpowerStatus OBJECT-TYPE
        SYNTAX INTEGER {
            unknown(1),
            ok(2),
            warning(3),
            alarm(4)
        }
        MAX-ACCESS read-only
        STATUS current
        DESCRIPTION
            "The status ok(2) indicates that the Rx power in the Channel 3 of QSFP+ is in
	    the normal level. The status warning(3) indicates that 
	    the Rx power in the Channel 3 exceeds high warning level or is below 
	    low warning level. The status alarm(4) indicates that the Rx power in the
	    Channel 3 exceeds high alarm level or is below low alarm level. 
	    If the fsFiberDDMSupportStatus is false or the Fiber module type is 
	    not QSFP+, the status is unknown(1)."
        ::= { fsFiberEntry 46 }

fsFiberChannel4RXpowerIntegerpart OBJECT-TYPE
        SYNTAX INTEGER
        MAX-ACCESS read-only
        STATUS current
        DESCRIPTION
            "The integer part of Rx power in Channel 4 of the QSFP+ 
	    Fiber module insered into the port. The value is in units of dbm.
	    If the fsFiberDDMSupportStatus is false or the Fiber module type is 
	    not QSFP+, the integer part of Rx power value in Channel 4 
	    is -100(means the value is invalid)."
        ::= { fsFiberEntry 47 }

fsFiberChannel4RXpowerDecimalpart OBJECT-TYPE
        SYNTAX INTEGER
        MAX-ACCESS read-only
        STATUS current
        DESCRIPTION
            "The decimal part of Rx power in Channel 4 of the QSFP+ 
	    Fiber module insered into the port. The value is in units of dbm.
	    If the fsFiberDDMSupportStatus is false or the Fiber module type is 
	    not QSFP+, the decimal part of Rx power value in Channel 4 
	    is -100(means the value is invalid)."
        ::= { fsFiberEntry 48 }

fsFiberChannel4RXpowertype OBJECT-TYPE
        SYNTAX INTEGER {
            unknown(1),
            average(2),
            oma(3)
        }
        MAX-ACCESS read-only
        STATUS current
        DESCRIPTION
            "The value indicates whether the received power measurement 
	     represents average input optical power(2) or oma(3) in Channel 4 of QSFP+. 
	     If the fsFiberDDMSupportStatus is false or the Fiber module type is 
	     not QSFP+, the value is unknown(1)."
        ::= { fsFiberEntry 49 }

fsFiberChannel4RXpowerStatus OBJECT-TYPE
        SYNTAX INTEGER {
            unknown(1),
            ok(2),
            warning(3),
            alarm(4)
        }
        MAX-ACCESS read-only
        STATUS current
        DESCRIPTION
            "The status ok(2) indicates that the Rx power in the Channel 4 of QSFP+ is in
	    the normal level. The status warning(3) indicates that 
	    the Rx power in the Channel 4 exceeds high warning level or is below 
	    low warning level. The status alarm(4) indicates that the Rx power in the
	    Channel 4 exceeds high alarm level or is below low alarm level. 
	    If the fsFiberDDMSupportStatus is false or the Fiber module type is 
	    not QSFP+, the status is unknown(1)."
        ::= { fsFiberEntry 50 }

fsFiberTXpowerIntegerpart OBJECT-TYPE
        SYNTAX INTEGER
        MAX-ACCESS read-only
        STATUS current
        DESCRIPTION
            "The integer part of Tx power of the Fiber module insered into the port.
	    The value is in units of dbm.
	    If the fsFiberDDMSupportStatus is false or the Fiber module type is 
	    neither SFP/SFP+ nor XFP, the integer part of Tx power value 
	    is -100(means that the value is invalid)."
        ::= { fsFiberEntry 51 }

fsFiberTXpowerDecimalpart OBJECT-TYPE
        SYNTAX INTEGER
        MAX-ACCESS read-only
        STATUS current
        DESCRIPTION
            "The decimal part of Tx power of the Fiber module insered into the port.
	    The value is in units of dbm.
	    If the fsFiberDDMSupportStatus is false or the Fiber module type is 
	    neither SFP/SFP+ nor XFP, the decimal part of Tx power value 
	    is -100(means that the value is invalid)."
        ::= { fsFiberEntry 52 }

fsFiberTXpowerStatus OBJECT-TYPE
        SYNTAX INTEGER {
            unknown(1),
            ok(2),
            warning(3),
            alarm(4)
        }
        MAX-ACCESS read-only
        STATUS current
        DESCRIPTION
            "The status ok(2) indicates that the Tx power of the Fiber module is in
	    the normal level. The status warning(3) indicates that the Tx power of 
	    the Fiber module exceeds high warning level or is below low warning level. 
            The status alarm(4) indicates that the Tx power of 
	    the Fiber module exceeds high alarm level or is below low alarm level. 
	    If the fsFiberDDMSupportStatus is false or the Fiber module type is 
	    neither SFP/SFP+ nor XFP, the status is unknown(1)."
        ::= { fsFiberEntry 53 }

fsFiberChannel1TXpowerIntegerpart OBJECT-TYPE
        SYNTAX INTEGER
        MAX-ACCESS read-only
        STATUS current
        DESCRIPTION
            "The integer part of Tx power in Channel 1 of the QSFP+ 
	    Fiber module insered into the port. The value is in units of dbm.
	    If the fsFiberDDMSupportStatus is false or the Fiber module type is 
	    not QSFP+, the integer part of Tx power value in Channel 1 
	    is -100(means the value is invalid)."
        ::= { fsFiberEntry 54 }

fsFiberChannel1TXpowerDecimalpart OBJECT-TYPE
        SYNTAX INTEGER
        MAX-ACCESS read-only
        STATUS current
        DESCRIPTION
            "The decimal part of Tx power in Channel 1 of the QSFP+ 
	    Fiber module insered into the port. The value is in units of dbm.
	    If the fsFiberDDMSupportStatus is false or the Fiber module type is 
	    not QSFP+, the decimal part of Tx power value in Channel 1 
	    is -100(means the value is invalid)."
        ::= { fsFiberEntry 55 }

fsFiberChannel1TXpowerStatus OBJECT-TYPE
        SYNTAX INTEGER {
            unknown(1),
            ok(2),
            warning(3),
            alarm(4)
        }
        MAX-ACCESS read-only
        STATUS current
        DESCRIPTION
            "The status ok(2) indicates that the Tx power in the Channel 1 of QSFP+ is in
	    the normal level. The status warning(3) indicates that 
	    the Tx power in the Channel 1 exceeds high warning level or is below 
	    low warning level. The status alarm(4) indicates that the Tx power in the
	    Channel 1 exceeds high alarm level or is below low alarm level. 
	    If the fsFiberDDMSupportStatus is false or the Fiber module type is 
	    not QSFP+, the status is unknown(1)."
        ::= { fsFiberEntry 56 }

fsFiberChannel2TXpowerIntegerpart OBJECT-TYPE
        SYNTAX INTEGER
        MAX-ACCESS read-only
        STATUS current
        DESCRIPTION
            "The integer part of Tx power in Channel 1 of the QSFP+ 
	    Fiber module insered into the port. The value is in units of dbm.
	    If the fsFiberDDMSupportStatus is false or the Fiber module type is 
	    not QSFP+, the integer part of Tx power value in Channel 1 
	    is -100(means the value is invalid)."
        ::= { fsFiberEntry 57 }

fsFiberChannel2TXpowerDecimalpart OBJECT-TYPE
        SYNTAX INTEGER
        MAX-ACCESS read-only
        STATUS current
        DESCRIPTION
            "The decimal part of Tx power in Channel 1 of the QSFP+ 
	    Fiber module insered into the port. The value is in units of dbm.
	    If the fsFiberDDMSupportStatus is false or the Fiber module type is 
	    not QSFP+, the decimal part of Tx power value in Channel 2 
	    is -100(means the value is invalid)."
        ::= { fsFiberEntry 58 }

fsFiberChannel2TXpowerStatus OBJECT-TYPE
        SYNTAX INTEGER {
            unknown(1),
            ok(2),
            warning(3),
            alarm(4)
        }
        MAX-ACCESS read-only
        STATUS current
        DESCRIPTION
            "The status ok(2) indicates that the Tx power in the Channel 2 of QSFP+ is in
	    the normal level. The status warning(3) indicates that 
	    the Tx power in the Channel 2 exceeds high warning level or is below 
	    low warning level. The status alarm(4) indicates that the Tx power in the
	    Channel 2 exceeds high alarm level or is below low alarm level. 
	    If the fsFiberDDMSupportStatus is false or the Fiber module type is 
	    not QSFP+, the status is unknown(1)."
        ::= { fsFiberEntry 59 }

fsFiberChannel3TXpowerIntegerpart OBJECT-TYPE
        SYNTAX INTEGER
        MAX-ACCESS read-only
        STATUS current
        DESCRIPTION
            "The integer part of Tx power in Channel 3 of the QSFP+ 
	    Fiber module insered into the port. The value is in units of dbm.
	    If the fsFiberDDMSupportStatus is false or the Fiber module type is 
	    not QSFP+, the integer part of Tx power value in Channel 3 
	    is -100(means the value is invalid)."
        ::= { fsFiberEntry 60 }

fsFiberChannel3TXpowerDecimalpart OBJECT-TYPE
        SYNTAX INTEGER
        MAX-ACCESS read-only
        STATUS current
        DESCRIPTION
            "The decimal part of Tx power in Channel 3 of the QSFP+ 
	    Fiber module insered into the port. The value is in units of dbm.
	    If the fsFiberDDMSupportStatus is false or the Fiber module type is 
	    not QSFP+, the decimal part of Tx power value in Channel 3 
	    is -100(means the value is invalid)."
        ::= { fsFiberEntry 61 }

fsFiberChannel3TXpowerStatus OBJECT-TYPE
        SYNTAX INTEGER {
            unknown(1),
            ok(2),
            warning(3),
            alarm(4)
        }
        MAX-ACCESS read-only
        STATUS current
        DESCRIPTION
            "The status ok(2) indicates that the Tx power in the Channel 3 of QSFP+ is in
	    the normal level. The status warning(3) indicates that 
	    the Tx power in the Channel 3 exceeds high warning level or is below 
	    low warning level. The status alarm(4) indicates that the Tx power in the
	    Channel 3 exceeds high alarm level or is below low alarm level. 
	    If the fsFiberDDMSupportStatus is false or the Fiber module type is 
	    not QSFP+, the status is unknown(1)."
        ::= { fsFiberEntry 62 }

fsFiberChannel4TXpowerIntegerpart OBJECT-TYPE
        SYNTAX INTEGER
        MAX-ACCESS read-only
        STATUS current
        DESCRIPTION
            "The integer part of Tx power in Channel 4 of the QSFP+ 
	    Fiber module insered into the port. The value is in units of dbm.
	    If the fsFiberDDMSupportStatus is false or the Fiber module type is 
	    not QSFP+, the integer part of Tx power value in Channel 4 
	    is -100(means the value is invalid)."
        ::= { fsFiberEntry 63 }

fsFiberChannel4TXpowerDecimalpart OBJECT-TYPE
        SYNTAX INTEGER
        MAX-ACCESS read-only
        STATUS current
        DESCRIPTION
            "The decimal part of Tx power in Channel 4 of the QSFP+ 
	    Fiber module insered into the port. The value is in units of dbm.
	    If the fsFiberDDMSupportStatus is false or the Fiber module type is 
	    not QSFP+, the decimal part of Tx power value in Channel 4 
	    is -100(means the value is invalid)."
        ::= { fsFiberEntry 64 }

fsFiberChannel4TXpowerStatus OBJECT-TYPE
        SYNTAX INTEGER {
            unknown(1),
            ok(2),
            warning(3),
            alarm(4)
        }
        MAX-ACCESS read-only
        STATUS current
        DESCRIPTION
            "The status ok(2) indicates that the Tx power in the Channel 4 of QSFP+ is in
	    the normal level. The status warning(3) indicates that 
	    the Tx power in the Channel 4 exceeds high warning level or is below 
	    low warning level. The status alarm(4) indicates that the Tx power in the
	    Channel 4 exceeds high alarm level or is below low alarm level. 
	    If the fsFiberDDMSupportStatus is false or the Fiber module type is 
	    not QSFP+, the status is unknown(1)."
        ::= { fsFiberEntry 65 }

fsFiberMIBConformance OBJECT IDENTIFIER ::= { fsFiberMIB 2 }
fsFiberMIBCompliances OBJECT IDENTIFIER ::= { fsFiberMIBConformance 1 }
fsFiberMIBGroups      OBJECT IDENTIFIER ::= { fsFiberMIBConformance 2 }

-- ---------------------------------------------------------- --
-- compliance statements
-- ---------------------------------------------------------- --
fsFiberMIBConpliance MODULE-COMPLIANCE
        STATUS  current
        DESCRIPTION
                "The compliance statement for entities which implement
                the FS Fiber MIB"
        MODULE  -- this module
                MANDATORY-GROUPS { 
                        fsFiberMIBGroup  
                }
         ::= { fsFiberMIBCompliances 1 }
         
fsFiberMIBGroup OBJECT-GROUP
        OBJECTS {
                fsFiberPortDescr,
                fsFiberTransceiverType,
                fsFiberConnectorType,
                fsFiberWavelength,
                fsFiberTransferDistanceSMF,
                fsFiberTransferDistance62point5umOM1,
                fsFiberTransferDistance62point5um,
                fsFiberTransferDistance50umOM2,
                fsFiberTransferDistance50um,
                fsFiberTransferDistance50umOM3,
                fsFiberTransferDistanceEBW50um,
                fsFiberTransferDistanceCopper,
                fsFiberTransferDistanceCableAssembly,
                fsFiberDDMSupportStatus,
                fsFiberSerialNumber,
                fsFiberTemp,
                fsFiberTempStatus,
                fsFiberVoltage,
                fsFiberVoltageStatus,
                fsFiberBias,
                fsFiberBiasStatus,
                fsFiberChannel1Bias,
                fsFiberChannel1BiasStatus,
                fsFiberChannel2Bias,
                fsFiberChannel2BiasStatus,
                fsFiberChannel3Bias,
                fsFiberChannel3BiasStatus,
                fsFiberChannel4Bias,
                fsFiberChannel4BiasStatus,
                fsFiberRXpowerIntegerpart,
                fsFiberRXpowerDecimalpart,
                fsFiberRXpowertype,
                fsFiberRXpowerStatus,
                fsFiberChannel1RXpowerIntegerpart,
                fsFiberChannel1RXpowerDecimalpart,
                fsFiberChannel1RXpowertype,
                fsFiberChannel1RXpowerStatus,
                fsFiberChannel2RXpowerIntegerpart,
                fsFiberChannel2RXpowerDecimalpart,
                fsFiberChannel2RXpowertype,
                fsFiberChannel2RXpowerStatus,
                fsFiberChannel3RXpowerIntegerpart,
                fsFiberChannel3RXpowerDecimalpart,
                fsFiberChannel3RXpowertype,
                fsFiberChannel3RXpowerStatus,
                fsFiberChannel4RXpowerIntegerpart,
                fsFiberChannel4RXpowerDecimalpart,
                fsFiberChannel4RXpowertype,
                fsFiberChannel4RXpowerStatus,
                fsFiberTXpowerIntegerpart,
                fsFiberTXpowerDecimalpart,
                fsFiberTXpowerStatus,
                fsFiberChannel1TXpowerIntegerpart,
                fsFiberChannel1TXpowerDecimalpart,
                fsFiberChannel1TXpowerStatus,
                fsFiberChannel2TXpowerIntegerpart,
                fsFiberChannel2TXpowerDecimalpart,
                fsFiberChannel2TXpowerStatus,
                fsFiberChannel3TXpowerIntegerpart,
                fsFiberChannel3TXpowerDecimalpart,
                fsFiberChannel3TXpowerStatus,
                fsFiberChannel4TXpowerIntegerpart,
                fsFiberChannel4TXpowerDecimalpart,
                fsFiberChannel4TXpowerStatus
        }
        STATUS  current
        DESCRIPTION
                "A collection of objects providing Fiber managment."
        ::= { fsFiberMIBGroups 1 }
END
